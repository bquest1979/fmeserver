FME workspace dwg2generic.fmw

Parameters:
- SourceDataset_ACAD = C:\Daten\_Veranstaltungen\20180411_FME_WT_Spanien\Automatizacion_de_flujos_de_datos\02_FME_Server_Basic\input\Parcels.dwg   # Source Autodesk AutoCAD DWG/DXF File/ Folder
- format = PDF2D
- DestDataset_GENERIC = C:\Daten\_Veranstaltungen\20180411_FME_WT_Spanien\Automatizacion_de_flujos_de_datos\02_FME_Server_Basic\output   # Destination Folder

Readers:
- ACAD_1: ACAD from $(SourceDataset_ACAD) in UTM83-10

Writers:
- GENERIC_1: GENERIC to $(DestDataset_GENERIC)

Note: Reader Feature Types
Note: Data Flow
Note: Writer Feature Types

Bookmark: Source Data
ParcelLines (reader ACAD_1)
    -> AreaBuilder

Bookmark: Building of Polygons
AreaBuilder
    ALLOW_CYCLES = No
    DONUT_CREATION = Yes
    DROP_HOLES = No
    LINES_AS_SEGMENTS = No
    SNAPTYPE_PARAM = None
    SNAP_TOLERANCE = 0
    AREA -> parcels (writer GENERIC_1)

Bookmark: Generic Writer
parcels (writer GENERIC_1)
